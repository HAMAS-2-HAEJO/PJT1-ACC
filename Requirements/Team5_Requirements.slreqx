# Team5_Requirements
OEM 4조 요구사항 - ACC(Adaptive Cruise Control) 및 빗물 감지 값에 따른 ACC 기능 구현, 와이퍼 동작 구현

## Req_001: 시스템 초기 상태 설정 (Functional)
시스템 작동 시, Default는 ACC off 모드로 설정되어야 한다. (LED 모두 off, Switch off)

## Req_004: [ACC off] 모터 최저 속도 % (Functional)
ACC off 모드에서, 가변저항 ADC 반환값 0일 때 모터 속도는 PWM 0%이다. (위 요구사항 수치와 비례하여 증감하도록 한다.)

## Req_005: ACC on/off 설정 (Functional)
(SW1) 스위치 버튼 1번을 터치 시, ACC on 모드로 전이되고 다시 1번 터치 시 ACC off 모드로 되어야 한다.

## Req_006: [Common] 모터 방향 전환 (Functional)
(SW2) 스위치 버튼 1초 이내 더블 클릭 시, 모터 방향이 반대로 전환되어야 한다. (속도 동일)

## Req_007: [Common] 브레이크 제어 (Functional)
(SW2) 스위치 버튼 1번을 터치 시, (PWM 조작이 아닌) 브레이크 드라이버로 직접 제동해야 한다.

## Req_008: [ACC on] 전방 객체 감지 시 거리 별 속도 제어 (5~25cm) (Functional)
전방 초음파 센서로부터 25cm 이내에 객체 존재 시, 5cm 마다 PWM이 10% 감속된다.

## Req_009: [ACC on] 전방 객체 감지 시 거리 별 부저 제어 (5~25cm) (Functional)
전방 초음파 센서로부터 25cm 이내 객체 존재 시, Buzzer를 주기적으로 울린다. 객체와의 거리가 가까워질수록 Buzzer 소리의 주기(임의주기, TBD)가 빨라진다.

## Req_010: [ACC on] 전방 객체 감지 시 거리 별 부저 제어 (5cm 이내) (Functional)
객체와의 거리가 5cm 이하일 때 Buzzer가 지속적으로 울리도록 한다.

## Req_011: [ACC on] 전방 객체 감지 시 거리 별 속도 제어 (5cm 이내) (Functional)
전방 초음파 센서로부터 5cm 이내 객체 존재 시, 모터 속도는 PWM 0%이며 차량은 정차한다.

## Req_012: [Common] 후진 시 LED 제어 (Functional)
차량 후진 시 LED(D13 - 파랑)를 점등한다.

## Req_013: [ACC on] 빗물 감지 값에 따른 속도제어 기준거리 조절 (Functional)
빗물 감지 센서 값이 800 이하일 때 우천 상황으로 판단하여, 차량 제동을 위한 초음파 센서 감지 거리를 5cm 증가시킨다.

## Req_014: [ACC on] 빗물 감지 값에 따른 거리 별 속도 제어 (Functional)
빗물 감지 센서 값이 800 이하일 때 우천 상황으로 판단하여, 10cm 마다 PWM이 15%씩 감소된다. (정지되는 거리가 짧아지는 것)

## Req_015: [Wiper] 와이퍼 on/off 및 작동 단계 설정 (Functional)
와이퍼 모드는 총 4단계(OFF, 1단계, 2단계, 3단계)로 이루어지며 와이퍼 ON/OFF SW3 으로 조절된다.

## Req_016: [Wiper] 와이퍼 1단계 시 작동 방식 (Functional)
와이퍼 OFF 상태에서 SW3을 터치시 1단계로 바뀌며, 와이퍼 PWM 80 상태로 (1초 동안 forward ↔ 1초 backward) 반복, LED3 ON

## Req_017: [Wiper] 와이퍼 2단계 시 작동 방식 (Functional)
와이퍼 1단계 상태에서 SW3을 터치시 2단계로 바뀌며, 와이퍼 PWM 140 상태로 (2초 동안 forward ↔ 2초 backward) 반복, LED3 ON

## Req_018: [Wiper] 와이퍼 3단계 시 작동 방식 (Functional)
와이퍼 2단계 상태에서 SW3을 터치 시 3단계로 바뀌며, 와이퍼 PWM 200상태로 (3초 동안 forward ↔ 3초 backward) 반복, LED3 ON

## Req_019: [Wiper] 와이퍼 OFF 작동 방식 (Functional)
와이퍼 3단계 상태에서 SW3을 터치 시 와이퍼 OFF 상태로 바뀌며, PWM = 0, LED3 OFF 상태가 됨

## Req_002: [Common] 모터 속도 범위 % (Functional)
모터 속도는 PWM 0% ~ 60% 이내로 한다.

## Req_003: [ACC off] 모터 최대 속도 % (Functional)
ACC off 모드에서, 가변저항 ADC 반환 값 1023일 때 모터 속도는 PWM 60%이다. (가변저항 분해능 256)
